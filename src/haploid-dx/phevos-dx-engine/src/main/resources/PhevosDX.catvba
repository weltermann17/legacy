Attribute VB_Name = "Reframe_Tiff"
' -----------------------------------------------------------------------------
' Script Copyright MAN Truck & Bus AG, 2011
' -----------------------------------------------------------------------------
' Description:
'   Script to prepare the tif files downloaded from ezis.
' -----------------------------------------------------------------------------
' ---------------------------------------------------------------
' Return Codes
' ---------------------------------------------------------------
' 1: Something went wrong
' TBD
'
' ---------------------------------------------------------------
' Constants
' ---------------------------------------------------------------
Public Const WIN = "Windows"
Public Const UNIX = "UNIX"

Public Const orig_catia_pn = "orig_catia_part_number"
Public Const orig_catia_filename = "orig_catia_filename"

Public Const param_prefix = "MTB_"

' ---------------------------------------------------------------
' Global variables
' ---------------------------------------------------------------
Dim g_strOS As String                   'UNIX or WIN
Dim g_strLogFilePath As String
Dim g_fileSystem As Object          'CATIA.FileSystem
Dim g_systemService As Object       'CATIA.SystemService
Dim g_systemConfig As Object        'CATIA.SystemConfiguration
Dim g_strSlash As String            ' / or \, depending on OS

Dim g_strCurrDir As String          'calculated from catia session filename

' Variables from environment
Dim g_str_mtb_part_number As String                 '85.41801-0100
Dim g_str_mtb_index As String                       '_A_
Dim g_str_mtb_drawing_date As String                '06/04/2012
Dim g_str_ml_change_number As String
Dim g_str_vw_part_number As String                  '.111.222.333.AA
Dim g_str_ml_pt_name As String                      'TANKO BRACKETO
Dim g_str_ml_en_name As String                      'TANK BRACKET

Dim dummyOutputString As String
Dim versiondummystring As String                    ' just to modify the .catvba file

Sub CATMain()

    versiondummystring = "20120706115700"
    
    ' -------------------------------------------------------------------------
    ' Init global vars
    ' -------------------------------------------------------------------------
    Set g_fileSystem = CATIA.FileSystem
    Set g_systemService = CATIA.SystemService
    Set g_systemConfig = CATIA.SystemConfiguration
    g_strLogFilePath = ""   ' forces to log to console only until filled

    If (g_systemConfig.OperatingSystem = "aix_a") Then
        g_strOS = UNIX
        g_strSlash = "/"
    Else
        g_strOS = WIN
        g_strSlash = "\"
    End If

    ' -------------------------------------------------------------------------
    ' Init local vars
    ' -------------------------------------------------------------------------
    Dim bOK As Boolean
    bOK = True

    ' -------------------------------------------------------------------------
    ' Get current directory from file open in Session
    ' -------------------------------------------------------------------------

    g_strCurrDir = ""

    If (0 = StrComp(g_strCurrDir, "")) Then
        Dim strWorkDirPath  As String
        If (True = GetEnvVars(strWorkDirPath)) Then
            g_strCurrDir = strWorkDirPath
        Else
            Call FatalError(1, "User env var PHEVOS_DX_USER_WORK_DIR must be set for this macro -> exiting")
            dummyOutputString = g_systemService.Print("User env var PHEVOS_DX_USER_WORK_DIR must be set for this macro -> exiting")
            CATIA.Quit
        End If
    End If

    Dim fileList
    Dim currentFolder
    Dim currFile

    Set currentFolder = g_fileSystem.GetFolder(g_strCurrDir)
    Set fileList = currentFolder.Files

    Dim strInputDir As String

    ' -------------------------------------------------------------------------
    ' Get all tif files in work dir and
    ' Check all tif files have template filename, exit with msg when not
    ' -------------------------------------------------------------------------
    Dim bTifExists As Boolean
    bTifExists = False
    Set fileList = currentFolder.Files

    For Each currFile In fileList
        If (Right(currFile.Name, 3) = "tif") Then

            bTifExists = True
            Call CreateCOPDrawing(currFile.Path, currFile.Name)
        End If
    Next

    If (False = bTifExists) Then
        Call FatalError(1, "No .tif files found in work_dir!")
        dummyOutputString = g_systemService.Print("No .tif files found in work_dir!")
    End If
    
    dummyOutputString = g_systemService.Print("Finished")

    ' -------------------------------------------------------------------------
    'Cleanup
    ' -------------------------------------------------------------------------
    Set g_fileSystem = Nothing
    Set g_systemService = Nothing
    Set g_systemConfig = Nothing

    CATIA.Quit
End Sub

' ---------------------------------------------------------------
' Gets variables from the environment
' ---------------------------------------------------------------
Function GetEnvVars(strWorkDirPath As String) As Boolean

    strWorkDirPath = g_systemService.Environ("PHEVOS_DX_USER_WORK_DIR")

    g_str_mtb_part_number = g_systemService.Environ("PHEVOS_DX_MTB_PART_NUMBER")

    g_str_mtb_index = g_systemService.Environ("PHEVOS_DX_MTB_INDEX")

    g_str_mtb_drawing_date = g_systemService.Environ("PHEVOS_DX_MTB_DRAWING_DATE")

    g_str_ml_change_number = g_systemService.Environ("PHEVOS_DX_ML_CHANGE_NUMBER")

    g_str_vw_part_number = g_systemService.Environ("PHEVOS_DX_VW_PART_NUMBER")

    g_str_ml_pt_name = g_systemService.Environ("PHEVOS_DX_ML_PT_NAME")

    g_str_ml_en_name = g_systemService.Environ("PHEVOS_DX_ML_EN_NAME")

    GetEnvVars = True

End Function

Sub CreateCOPDrawing(strTifFilePath As String, strNewFilename As String)

    Dim documents1
    Set documents1 = CATIA.Documents

    Dim drawingDocument1
    Set drawingDocument1 = documents1.Add("Drawing")

    Dim MySheet
    Set MySheet = CATIA.ActiveDocument.Sheets.Item("Sheet.1")
    MySheet.Activate

    ' Select the Main View, which is always Item(1)
    Dim MyView
    Set MyView = MySheet.Views.Item(1)

    Dim MyDrawingPicture1
    Set MyDrawingPicture1 = MyView.Pictures.Add(strTifFilePath, 0, 0)

    Dim origHeight, origWidth As Integer
    origHeight = MyDrawingPicture1.GetOriginalHeight
    origWidth = MyDrawingPicture1.GetOriginalWidth

    ' Height x Width
    ' Format A0 ISO = 841 x 1189 mm
    ' Format A1 ISO = 594 x 841 mm
    ' Format A2 ISO = 420 x 594 mm
    ' Format A3 ISO = 297 x 420 mm
    ' Format A4 ISO = 210 x 297 mm

    ' Tolerance in mm
    Dim tolerance As Integer
    tolerance = 5

    drawingDocument1.Close

    Dim strPathToDrwTemplates, strTemplate  As String
    strPathToDrwTemplates = g_strCurrDir

    If ((origHeight < (210 + tolerance)) And origWidth < (297 + tolerance)) Then

        'TIFF is A4, use A4 overlong or A3
        strTemplate = "A3_TEMPLATE.CATDrawing"

    ElseIf ((origHeight < (297 + tolerance)) And origWidth < (210 + tolerance)) Then

        'TIFF is A4 portrait, use A4 portrait
        strTemplate = "A4_PORTRAIT_TEMPLATE.CATDrawing"

    ElseIf ((origHeight < (297 + tolerance)) And origWidth < (420 + tolerance)) Then

        'TIFF is A3, use A3 overlong or A2
        strTemplate = "A3_TEMPLATE.CATDrawing"

    ElseIf ((origHeight < (420 + tolerance)) And origWidth < (594 + tolerance)) Then

        'TIFF is A2, use A2 overlong or A1
        strTemplate = "A2_TEMPLATE.CATDrawing"

    ElseIf ((origHeight < (594 + tolerance)) And origWidth < (841 + tolerance)) Then

        'TIFF is A1, use A1 overlong or A0
        strTemplate = "A1_TEMPLATE.CATDrawing"

    ElseIf ((origHeight < (841 + tolerance)) And origWidth < (1189 + tolerance)) Then

        'TIFF is A0, use A0 overlong or ?
        strTemplate = "A0_TEMPLATE.CATDrawing"

    Else
        Call FatalError(1, "Strange  TIFF size: H" & origHeight & " x W" & origWidth)
        dummyOutputString = g_systemService.Print("Strange  TIFF size: H" & origHeight & " x W" & origWidth)
        CATIA.Quit
    End If

    Set drawingDocument1 = documents1.Open(strPathToDrwTemplates & g_strSlash & strTemplate)

    Set MySheet = CATIA.ActiveDocument.Sheets.Item("Sheet.1")
    MySheet.Activate

    ' Select the Main View, which is always Item(1)
    Set MyView = MySheet.Views.Item(1)

    Set MyDrawingPicture1 = MyView.Pictures.Add(strTifFilePath, 0, 0)

    MySheet.Activate
    Set MyView = Nothing
    Set MyView = MySheet.Views.Item(2)
    MyView.Activate

    Dim DrwView2
    Dim DrwTexts
    Dim DrwText

    Set DrwView = MySheet.Views.ActiveView
    Set DrwTexts = DrwView.Texts

    Set DrwText = DrwTexts.GetItem("Phevos_partnr_le")
    DrwText.Text = g_str_vw_part_number

    'Set DrwText = DrwTexts.GetItem("Phevos_partnr_ri")
    DrwText.Text = g_str_vw_part_number

    Set DrwText = DrwTexts.GetItem("Phevos_benennung")
    DrwText.Text = g_str_ml_pt_name

    Set DrwText = DrwTexts.GetItem("Phevos_title")
    DrwText.Text = g_str_ml_en_name

    Set DrwText = DrwTexts.GetItem("Phevos_descr")
    DrwText.Text = g_str_ml_change_number

    Set DrwText = DrwTexts.GetItem("Phevos_date")
    Dim dteMl_drawing_date
    Dim strMl_drawing_date

    If IsDate(g_str_mtb_drawing_date) Then
        dteMl_drawing_date = CDate(g_str_mtb_drawing_date)
        strMl_drawing_date = Left(CStr(dteMl_drawing_date), 6) & Right(CStr(dteMl_drawing_date), 2)

    ElseIf (Not IsDate(g_str_mtb_drawing_date)) And (g_str_mtb_drawing_date <> "") Then
        Call FatalError(1, "The dateformat in the dx property file is invalid")
        dummyOutputString = g_systemService.Print("The dateformat in the dx property file is invalid")
        CATIA.Quit
    Else
        strMl_drawing_date = Left(CStr(Date), 6) & Right(CStr(Date), 2)

    End If
    DrwText.Text = strMl_drawing_date

    Set MyView = MySheet.Views.Item(1)
    MyView.Activate
    MySheet.Activate

    Call drawingDocument1.ExportData(g_strCurrDir & g_strSlash & strNewFilename, "tif")

End Sub

Sub FatalError(returncode As Integer, message As String)

    dummyOutputString = g_systemService.Print("###<Return Code> " & returncode)
    dummyOutputString = g_systemService.Print("###<Return Message> " & message)
    
    CATIA.Quit

End Sub
