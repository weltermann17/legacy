Attribute VB_Name = "Reframe_Tiff"
Option Explicit

Dim i As Integer

Sub log(level As String, msg As String)
    On Error Resume Next
    Debug.Print level & " : " & msg
    Dim sysserv As Object
    Set sysserv = CATIA.SystemService
    Dim s As String
    s = sysserv.Print(level & " : " & msg)
    i = i + 1
    CATIA.FileSystem.CreateFile Str(i) & ".txt", True
End Sub

Sub trace(msg As String)
    log "DEBUG", msg
End Sub

Sub info(msg As String)
    log "INFO", msg
End Sub

Sub warning(msg As String)
    log "WARNING", msg
End Sub

Sub severe(msg As String)
    log "SEVERE", msg
End Sub

Sub fatal(code As Integer, msg As String)
    log "FATAL", "{""fatalerror"":{""""returncode"":" & code & ",""message"":"" & msg & ""}}"
    CATIA.Quit
End Sub

Sub CATMain()

    On Error GoTo ExitMain
    
    CATIA.Interactive = False
    CATIA.DisplayFileAlerts = False

    trace "trace"
    info "info"
    warning "warning"
    severe "severe"
    fatal -1, "this is fatal"
    
ExitMain:
    CATIA.Quit
    
End Sub
